import os, traceback
try:
    target = os.path.join(os.path.dirname(__file__), "freecad_meshpart_smoke.py")
    namespace = {"__name__": "__main__", "__file__": target, "__package__": None}
    exec(compile(open(target, encoding="utf-8").read(), target, "exec"), namespace, namespace)
except BaseException:
    traceback.print_exc()
    os._exit(1)
os._exit(0)
