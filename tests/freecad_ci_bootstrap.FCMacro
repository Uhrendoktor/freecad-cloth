"""FreeCAD GUI acceptance bootstrap that defers work until startup returns."""
import os
import runpy
import sys
import traceback

ROOT = "/workspace"
script = os.environ["CLOTH_CI_SCRIPT"]

# Keep the repository out of FreeCAD's own delayed-startup import path.
sys.path[:] = [p for p in sys.path if p != ROOT]

try:
    from PySide import QtCore  # noqa: E402
except ImportError:
    try:
        from PySide2 import QtCore  # noqa: E402
    except ImportError:
        from PySide6 import QtCore  # noqa: E402


def _run_acceptance():
    import FreeCADGui as Gui
    try:
        from PySide import QtWidgets
    except ImportError:
        try:
            from PySide2 import QtWidgets
        except ImportError:
            from PySide6 import QtWidgets
    app = QtWidgets.QApplication.instance()
    try:
        window = Gui.getMainWindow()
        if window is None:
            raise RuntimeError("FreeCAD GUI main window is not available")
        window.show()
        if ROOT not in sys.path:
            sys.path.insert(0, ROOT)
        runpy.run_path(script, run_name="__main__")
    except BaseException:
        traceback.print_exc()
        if app is not None:
            app.exit(1)
        return
    if app is not None:
        app.exit(0)


# The macro may be reached through FreeCAD's startup file-processing path.
# Deferring the acceptance script prevents InitGui.py from re-entering startup.
# Wait an extra event-loop turn for FreeCAD delayed startup to finish all queued GUI work.
QtCore.QTimer.singleShot(100, _run_acceptance)
